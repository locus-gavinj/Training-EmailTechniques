FME workspace EmailTechniques.fmw
Title: Email Techniques
Description: Example workspace to show two different emailing techniques.
Created by Gavin Jeter, LOCUS
History: 2025-04-03,G Jeter,Initial Creation

Parameters:
- EMAIL_WEB_CONNECTION =   # "safe.emailer.Microsoft Mail" Email Web Connection (recommend Service Account)
- EMAIL_FROM = service.account@organization.com   # Email From (should match the Email Service Account)
- EMAIL_TO = first.last@organization.com,first2.last2@organization.com   # Email Received (comma-delimited)
- EMAIL_CC = monitored.inbox@organization.com   # Email Carbon-Copy (comma-delimited and monitored inbox account)
- FLOW_WEB_CONNECTION =   # "safe.emailer.Microsoft Mail" FME Flow Connection (recommend Service Account)

Note: When sending Emails, try to parameterize as much as you can. / In the Navigator window (left-hand sidebar), I've created feilds for the Sender and Receivers. / The main thing to consider is maintenance on FME Flow. - If all your emails use a FME Flow email service account, then everyone in the org can use that same web connection on FME Server.
Creator
    GEOMTYPE = Geometry Object
    NUM = 1
    CREATED -> HTTPCaller
Note: Example that we know will FAIL
HTTPCaller
    CLIENT_CERTIFICATE_TYPE = NONE
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://http
    TRANSFER_TIMEOUT_LENGTH = 90
    USE_COOKIES = No
    VERIFY_SSL_CERTIFICATES = Yes
    <REJECTED> -> AttributeCreator
Note: Important Message or Alert to be emailed
AttributeCreator
    ATTR_TABLE:
      SET_TO _subject (varchar(200)) = ALERT - $(WORKSPACE_NAME) Failed
      SET_TO _body (varchar(200)) = HTTPCaller Code: @Value(_http_status_code) Error: @Value(_error)
    -> Emailer
    -> FMEFlowEmailGenerator
Note: Safe Software's "out of the box" Emailer is pretty solid. - It's also maintained by the product team, so it's supported by the company, where the method below is not.
Note: SMTP - If using SMTP, you might consider using a Deployment Paramter for the Password, which could then be uploaded and shared across FME Flow. / Deployment Parameters are new - / Documentation: / Deployment Parameters
Emailer
    CC = $(EMAIL_CC)
    FROM = FMEFlow.ServiceAccount@organization
    SERVICE = Generic SMTP
    SMTP_CONNECTION = HOST;$(EMAIL_WEB_CONNECTION);PORT;25;ENCRYPTION;None;TIMEOUT;60;AUTHENTICATION;NO;USERNAME;<Unused>;PASSWORD;<Unused>;FME_CONTROLLER_QUERY_FILE;dependencies/Generic SMTP.fme;FME_CONTROLLER_CHOICE;Generic SMTP
    TO = $(EMAIL_TO)
Note: I've also been in an organization that used a Topic Monitoring method. / Trickier to setup, however it may provide a bit better logging in FME Flow, as it uses JSON objects to send the Notifications
FMEFlowEmailGenerator
    email_cc = $(EMAIL_CC)
    email_subject = @Value(_subject)
    email_subscriber_content = @Value(_body)
    email_to = $(EMAIL_TO)
    -> FMEFlowNotifier
FMEFlowNotifier
    BODY = @Value(text_line_data)
    SERVER_CONNECTION = $(FLOW_WEB_CONNECTION)
    TOPIC = EMAIL_HTML
